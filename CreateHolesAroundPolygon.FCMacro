# Version: 1.0.1
# CreateHolesAroundPolygon_v2_4.FCMacro
# FreeCAD 1.1+
# Robust perimeter hole generator using centroid-based inward offset

import FreeCAD as App
import Part
from PySide import QtGui
import math

DOC = App.ActiveDocument
if not DOC:
    raise RuntimeError("No active document")

EPS = 0.5  # mm breakthrough margin

# -------------------------------------------------
# helpers
# -------------------------------------------------

def select_from_list(title, label, objects):
    if len(objects) == 1:
        return objects[0]

    names = [o.Name for o in objects]
    choice, ok = QtGui.QInputDialog.getItem(
        None, title, label, names, 0, False
    )
    if not ok:
        raise RuntimeError("Cancelled")

    for o in objects:
        if o.Name == choice:
            return o

    raise RuntimeError("Invalid selection")

def get_bodies():
    return [o for o in DOC.Objects if o.TypeId == "PartDesign::Body"]

def get_pads(body):
    return [o for o in body.Group if o.TypeId == "PartDesign::Pad"]

# -------------------------------------------------
# user input
# -------------------------------------------------

hole_dia, ok = QtGui.QInputDialog.getDouble(
    None, "Hole Diameter", "mm", 5.0, 0.0
)
if not ok:
    raise RuntimeError

edge_offset, ok = QtGui.QInputDialog.getDouble(
    None, "Edge Offset", "mm", 10.0, 0.0
)
if not ok:
    raise RuntimeError

spacing, ok = QtGui.QInputDialog.getDouble(
    None, "Target Spacing", "mm", 10.0, 0.0
)
if not ok:
    raise RuntimeError

min_holes, ok = QtGui.QInputDialog.getInt(
    None, "Minimum holes per edge", "", 1, 1
)
if not ok:
    raise RuntimeError

# -------------------------------------------------
# select body / pad
# -------------------------------------------------

body = select_from_list("Select Body", "Body:", get_bodies())
pad  = select_from_list("Select Pad",  "Pad:",  get_pads(body))

# -------------------------------------------------
# select pad end face
# -------------------------------------------------

faces = pad.Shape.Faces
face_index = len(faces)
face = faces[face_index - 1]
face_name = f"Face{face_index}"

# Face centroid (critical for inward direction)
face_centroid = face.CenterOfMass

face_normal = face.normalAt(0.5, 0.5).normalize()
edges = face.OuterWire.Edges

# -------------------------------------------------
# cleanup (idempotent)
# -------------------------------------------------

for obj in list(body.Group):
    if obj.Name.startswith("PerimeterHole"):
        body.removeObject(obj)

DOC.recompute()

# -------------------------------------------------
# create sketch for points
# -------------------------------------------------

sketch = body.newObject(
    "Sketcher::SketchObject",
    "PerimeterHolePoints"
)
sketch.AttachmentSupport = [(pad, face_name)]
sketch.MapMode = "FlatFace"

DOC.recompute()

# -------------------------------------------------
# generate points
# -------------------------------------------------

for edge in edges:
    p0 = edge.Vertexes[0].Point
    p1 = edge.Vertexes[1].Point

    edge_vec = p1 - p0
    L = edge_vec.Length
    if L <= 0:
        continue

    usable = L - edge_offset * 2
    if usable <= 0:
        continue
   
    count = max(min_holes, int(usable / (spacing + hole_dia)))
    step = usable / (count + 1)

    edge_dir = edge_vec.normalize()

    # Two candidate perpendiculars
    perp1 = face_normal.cross(edge_dir).normalize()
    perp2 = perp1.negative()

    # Choose inward perpendicular using centroid
    mid = (p0 + p1) * 0.5
    test1 = mid + perp1
    test2 = mid + perp2

    if (face_centroid - test1).Length < (face_centroid - test2).Length:
        perp = perp1
    else:
        perp = perp2
	
	# Calculate the offset baased on half the diameter
    offset = (hole_dia / 2) + edge_offset

    for i in range(count):
		# Calculate distance along the edge from the start point
        d = edge_offset + (i + 1) * step

		# Determine the position on the edge and apply the perpendicular offset
        pt = p0 + edge_dir * d + perp * offset
        sketch.addGeometry(Part.Point(pt))

DOC.recompute()

# -------------------------------------------------
# create PartDesign Hole
# -------------------------------------------------

hole = body.newObject("PartDesign::Hole", "PerimeterHoles")
hole.Profile = sketch
hole.Diameter = hole_dia
hole.Depth = pad.Length.Value + EPS

DOC.recompute()
